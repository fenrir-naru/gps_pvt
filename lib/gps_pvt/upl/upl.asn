RRLP-Components DEFINITIONS AUTOMATIC TAGS ::=
BEGIN

VelocityEstimate ::= INTEGER

ExtensionContainer ::= INTEGER

MsrPosition-Req ::= SEQUENCE {
    positionInstruct	 PositionInstruct,
    referenceAssistData	 ReferenceAssistData OPTIONAL,
    msrAssistData	 MsrAssistData OPTIONAL,
    systemInfoAssistData	 SystemInfoAssistData OPTIONAL,
    gps-AssistData	 GPS-AssistData OPTIONAL,
    extensionContainer	 ExtensionContainer OPTIONAL,
    ...,
    rel98-MsrPosition-Req-extension	 Rel98-MsrPosition-Req-Extension OPTIONAL,
    rel5-MsrPosition-Req-extension	 Rel5-MsrPosition-Req-Extension OPTIONAL
}

MsrPosition-Rsp ::= SEQUENCE {
    multipleSets	 MultipleSets OPTIONAL,
    referenceIdentity	 ReferenceIdentity OPTIONAL,
    otd-MeasureInfo	 OTD-MeasureInfo OPTIONAL,
    locationInfo	 LocationInfo OPTIONAL,
    gps-MeasureInfo	 GPS-MeasureInfo OPTIONAL,
    locationError	 LocationError OPTIONAL,
    extensionContainer	 ExtensionContainer OPTIONAL,
    ...,
    rel-98-MsrPosition-Rsp-Extension	 Rel-98-MsrPosition-Rsp-Extension OPTIONAL,
    rel-5-MsrPosition-Rsp-Extension	 Rel-5-MsrPosition-Rsp-Extension OPTIONAL
}

AssistanceData ::= SEQUENCE {
    referenceAssistData	 ReferenceAssistData OPTIONAL,
    msrAssistData	 MsrAssistData OPTIONAL,
    systemInfoAssistData	 SystemInfoAssistData OPTIONAL,
    gps-AssistData	 GPS-AssistData OPTIONAL,
    moreAssDataToBeSent	 MoreAssDataToBeSent OPTIONAL,
    extensionContainer	 ExtensionContainer OPTIONAL,
    ...,
    rel98-AssistanceData-Extension	 Rel98-AssistanceData-Extension OPTIONAL,
    rel5-AssistanceData-Extension	 Rel5-AssistanceData-Extension OPTIONAL
}

ProtocolError ::= SEQUENCE {
    errorCause	 ErrorCodes,
    extensionContainer	 ExtensionContainer OPTIONAL,
    ...,
    rel-5-ProtocolError-Extension	 Rel-5-ProtocolError-Extension OPTIONAL
}

PositionInstruct ::= SEQUENCE {
    methodType	 MethodType,
    positionMethod	 PositionMethod,
    measureResponseTime	 MeasureResponseTime,
    useMultipleSets	 UseMultipleSets,
    environmentCharacter	 EnvironmentCharacter OPTIONAL
}

MethodType ::= CHOICE {
    msAssisted	 AccuracyOpt,
    msBased	 Accuracy,
    msBasedPref	 Accuracy,
    msAssistedPref	 Accuracy
}

AccuracyOpt ::= SEQUENCE {
    accuracy	 Accuracy OPTIONAL
}

Accuracy ::= INTEGER (0..127)

PositionMethod ::= ENUMERATED {
    eotd(0),
    gps(1),
    gpsOrEOTD(2)
}

MeasureResponseTime ::= INTEGER (0..7)

UseMultipleSets ::= ENUMERATED {
    multipleSets(0),
    oneSet(1)
}

EnvironmentCharacter ::= ENUMERATED {
    badArea(0),
    notBadArea(1),
    mixedArea(2),
    ...
}

ReferenceAssistData ::= SEQUENCE {
    bcchCarrier	 BCCHCarrier,
    bsic	 BSIC,
    timeSlotScheme	 TimeSlotScheme,
    btsPosition	 BTSPosition OPTIONAL
}

BTSPosition ::= Ext-GeographicalInformation

BCCHCarrier ::= INTEGER (0..1023)

BSIC ::= INTEGER (0..63)

TimeSlotScheme ::= ENUMERATED {
    equalLength(0),
    variousLength(1)
}

ModuloTimeSlot ::= INTEGER (0..3)

MsrAssistData ::= SEQUENCE {
    msrAssistList	 SeqOfMsrAssistBTS
}

SeqOfMsrAssistBTS ::= SEQUENCE (SIZE(1..15)) OF MsrAssistBTS

MsrAssistBTS ::= SEQUENCE {
    bcchCarrier	 BCCHCarrier,
    bsic	 BSIC,
    multiFrameOffset	 MultiFrameOffset,
    timeSlotScheme	 TimeSlotScheme,
    roughRTD	 RoughRTD,
    calcAssistanceBTS	 CalcAssistanceBTS OPTIONAL
}

MultiFrameOffset ::= INTEGER (0..51)

RoughRTD ::= INTEGER (0..1250)

SystemInfoAssistData ::= SEQUENCE {
    systemInfoAssistList	 SeqOfSystemInfoAssistBTS
}

SeqOfSystemInfoAssistBTS ::= SEQUENCE (SIZE(1..32)) OF SystemInfoAssistBTS

SystemInfoAssistBTS ::= CHOICE {
    notPresent	 NULL,
    present	 AssistBTSData
}

AssistBTSData ::= SEQUENCE {
    bsic	 BSIC,
    multiFrameOffset	 MultiFrameOffset,
    timeSlotScheme	 TimeSlotScheme,
    roughRTD	 RoughRTD,
    calcAssistanceBTS	 CalcAssistanceBTS OPTIONAL
}

CalcAssistanceBTS ::= SEQUENCE {
    fineRTD	 FineRTD,
    referenceWGS84	 ReferenceWGS84
}

ReferenceWGS84 ::= SEQUENCE {
    relativeNorth	 RelDistance,
    relativeEast	 RelDistance,
    relativeAlt	 RelativeAlt OPTIONAL
}

FineRTD ::= INTEGER (0..255)

RelDistance ::= INTEGER (-200000..200000)

RelativeAlt ::= INTEGER (-4000..4000)

MultipleSets ::= SEQUENCE {
    nbrOfSets	 INTEGER (2..3),
    nbrOfReferenceBTSs	 INTEGER (1..3),
    referenceRelation	 ReferenceRelation OPTIONAL
}

ReferenceRelation ::= ENUMERATED {
    secondBTSThirdSet(0),
    secondBTSSecondSet(1),
    firstBTSFirstSet(2)
}

ReferenceIdentity ::= SEQUENCE {
    refBTSList	 SeqOfReferenceIdentityType
}

SeqOfReferenceIdentityType ::= SEQUENCE (SIZE(1..3)) OF ReferenceIdentityType

ReferenceIdentityType ::= CHOICE {
    bsicAndCarrier	 BSICAndCarrier,
    ci	 CellID,
    requestIndex	 RequestIndex,
    systemInfoIndex	 SystemInfoIndex,
    ciAndLAC	 CellIDAndLAC
}

BSICAndCarrier ::= SEQUENCE {
    carrier	 BCCHCarrier,
    bsic	 BSIC
}

RequestIndex ::= INTEGER (1..16)

SystemInfoIndex ::= INTEGER (1..32)

CellIDAndLAC ::= SEQUENCE {
    referenceLAC	 LAC,
    referenceCI	 CellID
}

CellID ::= INTEGER (0..65535)

LAC ::= INTEGER (0..65535)

OTD-MeasureInfo ::= SEQUENCE {
    otdMsrFirstSets	 OTD-MsrElementFirst,
    otdMsrRestSets	 SeqOfOTD-MsrElementRest OPTIONAL
}

SeqOfOTD-MsrElementRest ::= SEQUENCE (SIZE(1..2)) OF OTD-MsrElementRest

OTD-MsrElementFirst ::= SEQUENCE {
    refFrameNumber	 INTEGER (0..42431),
    referenceTimeSlot	 ModuloTimeSlot,
    toaMeasurementsOfRef	 TOA-MeasurementsOfRef OPTIONAL,
    stdResolution	 StdResolution,
    taCorrection	 INTEGER (0..960) OPTIONAL,
    otd-FirstSetMsrs	 SeqOfOTD-FirstSetMsrs OPTIONAL
}

SeqOfOTD-FirstSetMsrs ::= SEQUENCE (SIZE(1..10)) OF OTD-FirstSetMsrs

OTD-MsrElementRest ::= SEQUENCE {
    refFrameNumber	 INTEGER (0..42431),
    referenceTimeSlot	 ModuloTimeSlot,
    toaMeasurementsOfRef	 TOA-MeasurementsOfRef OPTIONAL,
    stdResolution	 StdResolution,
    taCorrection	 INTEGER (0..960) OPTIONAL,
    otd-MsrsOfOtherSets	 SeqOfOTD-MsrsOfOtherSets OPTIONAL
}

SeqOfOTD-MsrsOfOtherSets ::= SEQUENCE (SIZE(1..10)) OF OTD-MsrsOfOtherSets

TOA-MeasurementsOfRef ::= SEQUENCE {
    refQuality	 RefQuality,
    numOfMeasurements	 NumOfMeasurements
}

RefQuality ::= INTEGER (0..31)

NumOfMeasurements ::= INTEGER (0..7)

StdResolution ::= INTEGER (0..3)

OTD-FirstSetMsrs ::= OTD-MeasurementWithID

OTD-MsrsOfOtherSets ::= CHOICE {
    identityNotPresent	 OTD-Measurement,
    identityPresent	 OTD-MeasurementWithID
}

OTD-Measurement ::= SEQUENCE {
    nborTimeSlot	 ModuloTimeSlot,
    eotdQuality	 EOTDQuality,
    otdValue	 OTDValue
}

OTD-MeasurementWithID ::= SEQUENCE {
    neighborIdentity	 NeighborIdentity,
    nborTimeSlot	 ModuloTimeSlot,
    eotdQuality	 EOTDQuality,
    otdValue	 OTDValue
}

EOTDQuality ::= SEQUENCE {
    nbrOfMeasurements	 INTEGER (0..7),
    stdOfEOTD	 INTEGER (0..31)
}

NeighborIdentity ::= CHOICE {
    bsicAndCarrier	 BSICAndCarrier,
    ci	 CellID,
    multiFrameCarrier	 MultiFrameCarrier,
    requestIndex	 RequestIndex,
    systemInfoIndex	 SystemInfoIndex,
    ciAndLAC	 CellIDAndLAC
}

MultiFrameCarrier ::= SEQUENCE {
    bcchCarrier	 BCCHCarrier,
    multiFrameOffset	 MultiFrameOffset
}

OTDValue ::= INTEGER (0..39999)

LocationInfo ::= SEQUENCE {
    refFrame	 INTEGER (0..65535),
    gpsTOW	 INTEGER (0..14399999) OPTIONAL,
    fixType	 FixType,
    posEstimate	 Ext-GeographicalInformation
}

FixType ::= INTEGER {
    twoDFix(0),
    threeDFix(1)
} (0..1)

GPS-MeasureInfo ::= SEQUENCE {
    gpsMsrSetList	 SeqOfGPS-MsrSetElement
}

SeqOfGPS-MsrSetElement ::= SEQUENCE (SIZE(1..3)) OF GPS-MsrSetElement

GPS-MsrSetElement ::= SEQUENCE {
    refFrame	 INTEGER (0..65535) OPTIONAL,
    gpsTOW	 GPSTOW24b,
    gps-msrList	 SeqOfGPS-MsrElement
}

GPSTOW24b ::= INTEGER (0..14399999)

SeqOfGPS-MsrElement ::= SEQUENCE (SIZE(1..16)) OF GPS-MsrElement

GPS-MsrElement ::= SEQUENCE {
    satelliteID	 SatelliteID,
    cNo	 INTEGER (0..63),
    doppler	 INTEGER (-32768..32767),
    wholeChips	 INTEGER (0..1022),
    fracChips	 INTEGER (0..1024),
    mpathIndic	 MpathIndic,
    pseuRangeRMSErr	 INTEGER (0..63)
}

MpathIndic ::= ENUMERATED {
    notMeasured(0),
    low(1),
    medium(2),
    high(3)
}

LocationError ::= SEQUENCE {
    locErrorReason	 LocErrorReason,
    additionalAssistanceData	 AdditionalAssistanceData OPTIONAL,
    ...
}

LocErrorReason ::= ENUMERATED {
    unDefined(0),
    notEnoughBTSs(1),
    notEnoughSats(2),
    eotdLocCalAssDataMissing(3),
    eotdAssDataMissing(4),
    gpsLocCalAssDataMissing(5),
    gpsAssDataMissing(6),
    methodNotSupported(7),
    notProcessed(8),
    refBTSForGPSNotServingBTS(9),
    refBTSForEOTDNotServingBTS(10),
    ...,
    notEnoughGANSSSats(11),
    ganssAssDataMissing(12),
    refBTSForGANSSNotServingBTS(13)
}

AdditionalAssistanceData ::= SEQUENCE {
    gpsAssistanceData	 GPSAssistanceData OPTIONAL,
    extensionContainer	 ExtensionContainer OPTIONAL,
    ...,
    ganssAssistanceData	 GANSSAssistanceData OPTIONAL
}

GPSAssistanceData ::= OCTET STRING (SIZE(1..maxGPSAssistanceData))

maxGPSAssistanceData INTEGER ::= 40

GANSSAssistanceData ::= OCTET STRING (SIZE(1..maxGANSSAssistanceData))

maxGANSSAssistanceData INTEGER ::= 40

ErrorCodes ::= ENUMERATED {
    unDefined(0),
    missingComponet(1),
    incorrectData(2),
    missingIEorComponentElement(3),
    messageTooShort(4),
    unknowReferenceNumber(5),
    ...
}

GPS-AssistData ::= SEQUENCE {
    controlHeader	 ControlHeader
}

MoreAssDataToBeSent ::= ENUMERATED {
    noMoreMessages(0),
    moreMessagesOnTheWay(1)
}

ControlHeader ::= SEQUENCE {
    referenceTime	 ReferenceTime OPTIONAL,
    refLocation	 RefLocation OPTIONAL,
    dgpsCorrections	 DGPSCorrections OPTIONAL,
    navigationModel	 NavigationModel OPTIONAL,
    ionosphericModel	 IonosphericModel OPTIONAL,
    utcModel	 UTCModel OPTIONAL,
    almanac	 Almanac OPTIONAL,
    acquisAssist	 AcquisAssist OPTIONAL,
    realTimeIntegrity	 SeqOf-BadSatelliteSet OPTIONAL
}

ReferenceTime ::= SEQUENCE {
    gpsTime	 GPSTime,
    gsmTime	 GSMTime OPTIONAL,
    gpsTowAssist	 GPSTOWAssist OPTIONAL
}

GPSTime ::= SEQUENCE {
    gpsTOW23b	 GPSTOW23b,
    gpsWeek	 GPSWeek
}

GPSTOW23b ::= INTEGER (0..7559999)

GPSWeek ::= INTEGER (0..1023)

GPSTOWAssist ::= SEQUENCE (SIZE(1..12)) OF GPSTOWAssistElement

GPSTOWAssistElement ::= SEQUENCE {
    satelliteID	 SatelliteID,
    tlmWord	 TLMWord,
    antiSpoof	 AntiSpoofFlag,
    alert	 AlertFlag,
    tlmRsvdBits	 TLMReservedBits
}

TLMWord ::= INTEGER (0..16383)

AntiSpoofFlag ::= INTEGER (0..1)

AlertFlag ::= INTEGER (0..1)

TLMReservedBits ::= INTEGER (0..3)

GSMTime ::= SEQUENCE {
    bcchCarrier	 BCCHCarrier,
    bsic	 BSIC,
    frameNumber	 FrameNumber,
    timeSlot	 TimeSlot,
    bitNumber	 BitNumber
}

FrameNumber ::= INTEGER (0..2097151)

TimeSlot ::= INTEGER (0..7)

BitNumber ::= INTEGER (0..156)

RefLocation ::= SEQUENCE {
    threeDLocation	 Ext-GeographicalInformation
}

DGPSCorrections ::= SEQUENCE {
    gpsTOW	 INTEGER (0..604799),
    status	 INTEGER (0..7),
    satList	 SeqOfSatElement
}

SeqOfSatElement ::= SEQUENCE (SIZE(1..16)) OF SatElement

SatElement ::= SEQUENCE {
    satelliteID	 SatelliteID,
    iode	 INTEGER (0..239),
    udre	 INTEGER (0..3),
    pseudoRangeCor	 INTEGER (-2047..2047),
    rangeRateCor	 INTEGER (-127..127),
    deltaPseudoRangeCor2	 INTEGER (-127..127),
    deltaRangeRateCor2	 INTEGER (-7..7),
    deltaPseudoRangeCor3	 INTEGER (-127..127),
    deltaRangeRateCor3	 INTEGER (-7..7)
}

SatelliteID ::= INTEGER (0..63)

NavigationModel ::= SEQUENCE {
    navModelList	 SeqOfNavModelElement
}

SeqOfNavModelElement ::= SEQUENCE (SIZE(1..16)) OF NavModelElement

NavModelElement ::= SEQUENCE {
    satelliteID	 SatelliteID,
    satStatus	 SatStatus
}

SatStatus ::= CHOICE {
    newSatelliteAndModelUC	 UncompressedEphemeris,
    oldSatelliteAndModel	 NULL,
    newNaviModelUC	 UncompressedEphemeris,
    ...
}

UncompressedEphemeris ::= SEQUENCE {
    ephemCodeOnL2	 INTEGER (0..3),
    ephemURA	 INTEGER (0..15),
    ephemSVhealth	 INTEGER (0..63),
    ephemIODC	 INTEGER (0..1023),
    ephemL2Pflag	 INTEGER (0..1),
    ephemSF1Rsvd	 EphemerisSubframe1Reserved,
    ephemTgd	 INTEGER (-128..127),
    ephemToc	 INTEGER (0..37799),
    ephemAF2	 INTEGER (-128..127),
    ephemAF1	 INTEGER (-32768..32767),
    ephemAF0	 INTEGER (-2097152..2097151),
    ephemCrs	 INTEGER (-32768..32767),
    ephemDeltaN	 INTEGER (-32768..32767),
    ephemM0	 INTEGER (-2147483648..2147483647),
    ephemCuc	 INTEGER (-32768..32767),
    ephemE	 INTEGER (0..4294967295),
    ephemCus	 INTEGER (-32768..32767),
    ephemAPowerHalf	 INTEGER (0..4294967295),
    ephemToe	 INTEGER (0..37799),
    ephemFitFlag	 INTEGER (0..1),
    ephemAODA	 INTEGER (0..31),
    ephemCic	 INTEGER (-32768..32767),
    ephemOmegaA0	 INTEGER (-2147483648..2147483647),
    ephemCis	 INTEGER (-32768..32767),
    ephemI0	 INTEGER (-2147483648..2147483647),
    ephemCrc	 INTEGER (-32768..32767),
    ephemW	 INTEGER (-2147483648..2147483647),
    ephemOmegaADot	 INTEGER (-8388608..8388607),
    ephemIDot	 INTEGER (-8192..8191)
}

EphemerisSubframe1Reserved ::= SEQUENCE {
    reserved1	 INTEGER (0..8388607),
    reserved2	 INTEGER (0..16777215),
    reserved3	 INTEGER (0..16777215),
    reserved4	 INTEGER (0..65535)
}

IonosphericModel ::= SEQUENCE {
    alfa0	 INTEGER (-128..127),
    alfa1	 INTEGER (-128..127),
    alfa2	 INTEGER (-128..127),
    alfa3	 INTEGER (-128..127),
    beta0	 INTEGER (-128..127),
    beta1	 INTEGER (-128..127),
    beta2	 INTEGER (-128..127),
    beta3	 INTEGER (-128..127)
}

UTCModel ::= SEQUENCE {
    utcA1	 INTEGER (-8388608..8388607),
    utcA0	 INTEGER (-2147483648..2147483647),
    utcTot	 INTEGER (0..255),
    utcWNt	 INTEGER (0..255),
    utcDeltaTls	 INTEGER (-128..127),
    utcWNlsf	 INTEGER (0..255),
    utcDN	 INTEGER (-128..127),
    utcDeltaTlsf	 INTEGER (-128..127)
}

Almanac ::= SEQUENCE {
    alamanacWNa	 INTEGER (0..255),
    almanacList	 SeqOfAlmanacElement
}

SeqOfAlmanacElement ::= SEQUENCE (SIZE(1..64)) OF AlmanacElement

AlmanacElement ::= SEQUENCE {
    satelliteID	 SatelliteID,
    almanacE	 INTEGER (0..65535),
    alamanacToa	 INTEGER (0..255),
    almanacKsii	 INTEGER (-32768..32767),
    almanacOmegaDot	 INTEGER (-32768..32767),
    almanacSVhealth	 INTEGER (0..255),
    almanacAPowerHalf	 INTEGER (0..16777215),
    almanacOmega0	 INTEGER (-8388608..8388607),
    almanacW	 INTEGER (-8388608..8388607),
    almanacM0	 INTEGER (-8388608..8388607),
    almanacAF0	 INTEGER (-1024..1023),
    almanacAF1	 INTEGER (-1024..1023)
}

AcquisAssist ::= SEQUENCE {
    timeRelation	 TimeRelation,
    acquisList	 SeqOfAcquisElement
}

SeqOfAcquisElement ::= SEQUENCE (SIZE(1..16)) OF AcquisElement

TimeRelation ::= SEQUENCE {
    gpsTOW	 GPSTOW23b,
    gsmTime	 GSMTime OPTIONAL
}

AcquisElement ::= SEQUENCE {
    svid	 SatelliteID,
    doppler0	 INTEGER (-2048..2047),
    addionalDoppler	 AddionalDopplerFields OPTIONAL,
    codePhase	 INTEGER (0..1022),
    intCodePhase	 INTEGER (0..19),
    gpsBitNumber	 INTEGER (0..3),
    codePhaseSearchWindow	 INTEGER (0..15),
    addionalAngle	 AddionalAngleFields OPTIONAL
}

AddionalDopplerFields ::= SEQUENCE {
    doppler1	 INTEGER (0..63),
    dopplerUncertainty	 INTEGER (0..7)
}

AddionalAngleFields ::= SEQUENCE {
    azimuth	 INTEGER (0..31),
    elevation	 INTEGER (0..7)
}

SeqOf-BadSatelliteSet ::= SEQUENCE (SIZE(1..16)) OF SatelliteID

Rel98-MsrPosition-Req-Extension ::= SEQUENCE {
    rel98-Ext-ExpOTD	 Rel98-Ext-ExpOTD OPTIONAL,
    ...,
    gpsTimeAssistanceMeasurementRequest	 NULL OPTIONAL,
    gpsReferenceTimeUncertainty	 GPSReferenceTimeUncertainty OPTIONAL
}

Rel98-AssistanceData-Extension ::= SEQUENCE {
    rel98-Ext-ExpOTD	 Rel98-Ext-ExpOTD OPTIONAL,
    ...,
    gpsTimeAssistanceMeasurementRequest	 NULL OPTIONAL,
    gpsReferenceTimeUncertainty	 GPSReferenceTimeUncertainty OPTIONAL
}

Rel98-Ext-ExpOTD ::= SEQUENCE {
    msrAssistData-R98-ExpOTD	 MsrAssistData-R98-ExpOTD OPTIONAL,
    systemInfoAssistData-R98-ExpOTD	 SystemInfoAssistData-R98-ExpOTD OPTIONAL
}

MsrAssistData-R98-ExpOTD ::= SEQUENCE {
    msrAssistList-R98-ExpOTD	 SeqOfMsrAssistBTS-R98-ExpOTD
}

SeqOfMsrAssistBTS-R98-ExpOTD ::= SEQUENCE (SIZE(1..15)) OF MsrAssistBTS-R98-ExpOTD

MsrAssistBTS-R98-ExpOTD ::= SEQUENCE {
    expectedOTD	 ExpectedOTD,
    expOTDUncertainty	 ExpOTDUncertainty
}

SystemInfoAssistData-R98-ExpOTD ::= SEQUENCE {
    systemInfoAssistListR98-ExpOTD	 SeqOfSystemInfoAssistBTS-R98-ExpOTD
}

SeqOfSystemInfoAssistBTS-R98-ExpOTD ::= SEQUENCE (SIZE(1..32)) OF SystemInfoAssistBTS-R98-ExpOTD

SystemInfoAssistBTS-R98-ExpOTD ::= CHOICE {
    notPresent	 NULL,
    present	 AssistBTSData-R98-ExpOTD
}

AssistBTSData-R98-ExpOTD ::= SEQUENCE {
    expectedOTD	 ExpectedOTD,
    expOTDuncertainty	 ExpOTDUncertainty
}

ExpectedOTD ::= INTEGER (0..1250)

ExpOTDUncertainty ::= INTEGER (0..7)

GPSReferenceTimeUncertainty ::= INTEGER (0..127)

GPSTimeAssistanceMeasurements ::= SEQUENCE {
    referenceFrameMSB	 INTEGER (0..63),
    gpsTowSubms	 INTEGER (0..9999) OPTIONAL,
    deltaTow	 INTEGER (0..127) OPTIONAL,
    gpsReferenceTimeUncertainty	 GPSReferenceTimeUncertainty OPTIONAL
}

Rel-98-MsrPosition-Rsp-Extension ::= SEQUENCE {
    rel-98-Ext-MeasureInfo	 SEQUENCE {
        otd-MeasureInfo-R98-Ext	 OTD-MeasureInfo-R98-Ext OPTIONAL
    },
    ...,
    timeAssistanceMeasurements	 GPSTimeAssistanceMeasurements OPTIONAL
}

OTD-MeasureInfo-R98-Ext ::= SEQUENCE {
    otdMsrFirstSets-R98-Ext	 OTD-MsrElementFirst-R98-Ext
}

OTD-MsrElementFirst-R98-Ext ::= SEQUENCE {
    otd-FirstSetMsrs-R98-Ext	 SeqOfOTD-FirstSetMsrs-R98-Ext OPTIONAL
}

SeqOfOTD-FirstSetMsrs-R98-Ext ::= SEQUENCE (SIZE(1..5)) OF OTD-FirstSetMsrs

Rel-5-MsrPosition-Rsp-Extension ::= SEQUENCE {
    extended-reference	 Extended-reference OPTIONAL,
    otd-MeasureInfo-5-Ext	 OTD-MeasureInfo-5-Ext OPTIONAL,
    ulPseudoSegInd	 UlPseudoSegInd OPTIONAL,
    ...
}

Extended-reference ::= SEQUENCE {
    smlc-code	 INTEGER (0..63),
    transaction-ID	 INTEGER (0..262143)
}

OTD-MeasureInfo-5-Ext ::= SeqOfOTD-MsrElementRest

UlPseudoSegInd ::= ENUMERATED {
    firstOfMany(0),
    secondOfMany(1)
}

Rel5-MsrPosition-Req-Extension ::= SEQUENCE {
    extended-reference	 Extended-reference,
    ...
}

Rel5-AssistanceData-Extension ::= SEQUENCE {
    extended-reference	 Extended-reference,
    ...
}

Rel-5-ProtocolError-Extension ::= SEQUENCE {
    extended-reference	 Extended-reference OPTIONAL,
    ...
}

Rel7-MsrPosition-Req-Extension ::= SEQUENCE {
    velocityRequested	 NULL OPTIONAL,
    ganssPositionMethod	 GANSSPositioningMethod OPTIONAL,
    ganss-AssistData	 GANSS-AssistData OPTIONAL,
    ganssCarrierPhaseMeasurementRequest	 NULL OPTIONAL,
    ganssTODGSMTimeAssociationMeasurementRequest	 NULL OPTIONAL,
    requiredResponseTime	 RequiredResponseTime OPTIONAL,
    ...
}

GANSSPositioningMethod ::= BIT STRING {
    gps(0),
    galileo(1)
} (SIZE(2..16))

GANSS-AssistData ::= SEQUENCE {
    ganss-controlHeader	 GANSS-ControlHeader
}

GANSS-ControlHeader ::= SEQUENCE {
    ganssCommonAssistData	 GANSSCommonAssistData OPTIONAL,
    ganssGenericAssistDataList	 SeqOfGANSSGenericAssistDataElement OPTIONAL
}

GANSSCommonAssistData ::= SEQUENCE {
    ganssReferenceTime	 GANSSReferenceTime OPTIONAL,
    ganssRefLocation	 GANSSRefLocation OPTIONAL,
    ganssIonosphericModel	 GANSSIonosphericModel OPTIONAL,
    ...
}

SeqOfGANSSGenericAssistDataElement ::= SEQUENCE (SIZE(1..8)) OF GANSSGenericAssistDataElement

GANSSGenericAssistDataElement ::= SEQUENCE {
    ganssID	 INTEGER (0..7) OPTIONAL,
    ganssTimeModel	 SeqOfGANSSTimeModel OPTIONAL,
    ganssDiffCorrections	 GANSSDiffCorrections OPTIONAL,
    ganssNavigationModel	 GANSSNavModel OPTIONAL,
    ganssRealTimeIntegrity	 GANSSRealTimeIntegrity OPTIONAL,
    ganssDataBitAssist	 GANSSDataBitAssist OPTIONAL,
    ganssRefMeasurementAssist	 GANSSRefMeasurementAssist OPTIONAL,
    ganssAlmanacModel	 GANSSAlmanacModel OPTIONAL,
    ganssUTCModel	 GANSSUTCModel OPTIONAL,
    ...
}

GANSSReferenceTime ::= SEQUENCE {
    ganssRefTimeInfo	 GANSSRefTimeInfo,
    ganssTOD-GSMTimeAssociation	 GANSSTOD-GSMTimeAssociation OPTIONAL
}

GANSSRefTimeInfo ::= SEQUENCE {
    ganssDay	 INTEGER (0..8191) OPTIONAL,
    ganssTOD	 GANSSTOD,
    ganssTODUncertainty	 GANSSTODUncertainty OPTIONAL,
    ganssTimeID	 INTEGER (0..7) OPTIONAL
}

GANSSTOD ::= INTEGER (0..86399)

GANSSTODUncertainty ::= INTEGER (0..127)

GANSSTOD-GSMTimeAssociation ::= SEQUENCE {
    bcchCarrier	 BCCHCarrier,
    bsic	 BSIC,
    frameNumber	 FrameNumber,
    timeSlot	 TimeSlot,
    bitNumber	 BitNumber,
    frameDrift	 FrameDrift OPTIONAL
}

FrameDrift ::= INTEGER (-64..63)

GANSSRefLocation ::= SEQUENCE {
    threeDLocation	 Ext-GeographicalInformation
}

GANSSIonosphericModel ::= SEQUENCE {
    ganssIonoModel	 GANSSIonosphereModel,
    ganssIonoStormFlags	 GANSSIonoStormFlags OPTIONAL,
    ...
}

GANSSIonosphereModel ::= SEQUENCE {
    ai0	 INTEGER (0..4095),
    ai1	 INTEGER (0..4095),
    ai2	 INTEGER (0..4095)
}

GANSSIonoStormFlags ::= SEQUENCE {
    ionoStormFlag1	 INTEGER (0..1),
    ionoStormFlag2	 INTEGER (0..1),
    ionoStormFlag3	 INTEGER (0..1),
    ionoStormFlag4	 INTEGER (0..1),
    ionoStormFlag5	 INTEGER (0..1)
}

SeqOfGANSSTimeModel ::= SEQUENCE (SIZE(1..7)) OF GANSSTimeModelElement

GANSSTimeModelElement ::= SEQUENCE {
    ganssTimeModelRefTime	 INTEGER (0..65535),
    tA0	 TA0,
    tA1	 TA1 OPTIONAL,
    tA2	 TA2 OPTIONAL,
    gnssTOID	 INTEGER (0..7),
    weekNumber	 INTEGER (0..8191) OPTIONAL
}

TA0 ::= INTEGER (-2147483648..2147483647)

TA1 ::= INTEGER (-8388608..8388607)

TA2 ::= INTEGER (-64..63)

GANSSDiffCorrections ::= SEQUENCE {
    dganssRefTime	 INTEGER (0..119),
    sgnTypeList	 SeqOfSgnTypeElement
}

SeqOfSgnTypeElement ::= SEQUENCE (SIZE(1..3)) OF SgnTypeElement

SgnTypeElement ::= SEQUENCE {
    ganssSignalID	 GANSSSignalID OPTIONAL,
    ganssStatusHealth	 INTEGER (0..7),
    dganssSgnList	 SeqOfDGANSSSgnElement
}

GANSSSignalID ::= INTEGER (0..3)

SeqOfDGANSSSgnElement ::= SEQUENCE (SIZE(1..16)) OF DGANSSSgnElement

DGANSSSgnElement ::= SEQUENCE {
    svID	 SVID,
    iod	 INTEGER (0..1023),
    udre	 INTEGER (0..3),
    pseudoRangeCor	 INTEGER (-2047..2047),
    rangeRateCor	 INTEGER (-127..127)
}

SVID ::= INTEGER (0..63)

GANSSNavModel ::= SEQUENCE {
    nonBroadcastIndFlag	 INTEGER (0..1),
    toeMSB	 INTEGER (0..31) OPTIONAL,
    eMSB	 INTEGER (0..127) OPTIONAL,
    sqrtAMBS	 INTEGER (0..63) OPTIONAL,
    ganssSatelliteList	 SeqOfGANSSSatelliteElement
}

SeqOfGANSSSatelliteElement ::= SEQUENCE (SIZE(1..32)) OF GANSSSatelliteElement

GANSSSatelliteElement ::= SEQUENCE {
    svID	 SVID,
    svHealth	 INTEGER (-7..13),
    iod	 INTEGER (0..1023),
    ganssClockModel	 GANSSClockModel,
    ganssOrbitModel	 GANSSOrbitModel,
    ...
}

GANSSOrbitModel ::= CHOICE {
    keplerianSet	 NavModel-KeplerianSet,
    ...
}

NavModel-KeplerianSet ::= SEQUENCE {
    keplerToeLSB	 INTEGER (0..511),
    keplerW	 INTEGER (-2147483648..2147483647),
    keplerDeltaN	 INTEGER (-32768..32767),
    keplerM0	 INTEGER (-2147483648..2147483647),
    keplerOmegaDot	 INTEGER (-8388608..8388607),
    keplerELSB	 INTEGER (0..33554431),
    keplerIDot	 INTEGER (-8192..8191),
    keplerAPowerHalfLSB	 INTEGER (0..67108863),
    keplerI0	 INTEGER (-2147483648..2147483647),
    keplerOmega0	 INTEGER (-2147483648..2147483647),
    keplerCrs	 INTEGER (-32768..32767),
    keplerCis	 INTEGER (-32768..32767),
    keplerCus	 INTEGER (-32768..32767),
    keplerCrc	 INTEGER (-32768..32767),
    keplerCic	 INTEGER (-32768..32767),
    keplerCuc	 INTEGER (-32768..32767)
}

GANSSClockModel ::= CHOICE {
    standardClockModelList	 SeqOfStandardClockModelElement,
    ...
}

SeqOfStandardClockModelElement ::= SEQUENCE (SIZE(1..2)) OF StandardClockModelElement

StandardClockModelElement ::= SEQUENCE {
    stanClockTocLSB	 INTEGER (0..511),
    stanClockAF2	 INTEGER (-2048..2047),
    stanClockAF1	 INTEGER (-131072..131071),
    stanClockAF0	 INTEGER (-134217728..134217727),
    stanClockTgd	 INTEGER (-512..511) OPTIONAL,
    stanModelID	 INTEGER (0..1) OPTIONAL,
    ...
}

GANSSRealTimeIntegrity ::= SEQUENCE {
    ganssBadSignalList	 SeqOfBadSignalElement
}

SeqOfBadSignalElement ::= SEQUENCE (SIZE(1..16)) OF BadSignalElement

BadSignalElement ::= SEQUENCE {
    badSVID	 SVID,
    badSignalID	 INTEGER (0..3) OPTIONAL
}

GANSSDataBitAssist ::= SEQUENCE {
    ganssTOD	 INTEGER (0..59),
    svID	 SVID,
    ganssDataTypeID	 INTEGER (0..2),
    ganssDataBits	 SeqOf-GANSSDataBits
}

SeqOf-GANSSDataBits ::= SEQUENCE (SIZE(1..1024)) OF GANSSDataBit

GANSSDataBit ::= INTEGER (0..1)

GANSSRefMeasurementAssist ::= SEQUENCE {
    ganssSignalID	 INTEGER (0..3) OPTIONAL,
    ganssRefMeasAssitList	 SeqOfGANSSRefMeasurementElement
}

SeqOfGANSSRefMeasurementElement ::= SEQUENCE (SIZE(1..16)) OF GANSSRefMeasurementElement

GANSSRefMeasurementElement ::= SEQUENCE {
    svID	 SVID,
    doppler0	 INTEGER (-2048..2047),
    additionalDoppler	 AdditionalDopplerFields OPTIONAL,
    codePhase	 INTEGER (0..1022),
    intCodePhase	 INTEGER (0..127),
    codePhaseSearchWindow	 INTEGER (0..31),
    additionalAngle	 AddionalAngleFields OPTIONAL,
    ...
}

AdditionalDopplerFields ::= SEQUENCE {
    doppler1	 INTEGER (0..63),
    dopplerUncertainty	 INTEGER (0..4)
}

GANSSAlmanacModel ::= SEQUENCE {
    weekNumber	 INTEGER (0..255),
    svIDMask	 SVIDMASK,
    toa	 INTEGER (0..255) OPTIONAL,
    ioda	 INTEGER (0..3) OPTIONAL,
    ganssAlmanacList	 SeqOfGANSSAlmanacElement
}

SVIDMASK ::= BIT STRING (SIZE(1..36))

SeqOfGANSSAlmanacElement ::= SEQUENCE (SIZE(1..36)) OF GANSSAlmanacElement

GANSSAlmanacElement ::= CHOICE {
    keplerianAlmanacSet	 Almanac-KeplerianSet,
    ...
}

Almanac-KeplerianSet ::= SEQUENCE {
    kepAlmanacE	 INTEGER (0..2047),
    kepAlmanacDeltaI	 INTEGER (-1024..1023),
    kepAlmanacOmegaDot	 INTEGER (-1024..1023),
    kepSVHealth	 INTEGER (0..15),
    kepAlmanacAPowerHalf	 INTEGER (-65536..65535),
    kepAlmanacOmega0	 INTEGER (-32768..32767),
    kepAlmanacW	 INTEGER (-32768..32767),
    kepAlmanacM0	 INTEGER (-32768..32767),
    kepAlmanacAF0	 INTEGER (-8192..8191),
    kepAlmanacAF1	 INTEGER (-1024..1023)
}

GANSSUTCModel ::= SEQUENCE {
    ganssUtcA1	 INTEGER (-8388608..8388607),
    ganssUtcA0	 INTEGER (-2147483648..2147483647),
    ganssUtcTot	 INTEGER (0..255),
    ganssUtcWNt	 INTEGER (0..255),
    ganssUtcDeltaTls	 INTEGER (-128..127),
    ganssUtcWNlsf	 INTEGER (0..255),
    ganssUtcDN	 INTEGER (-128..127),
    ganssUtcDeltaTlsf	 INTEGER (-128..127)
}

RequiredResponseTime ::= INTEGER (1..128)

Rel-7-MsrPosition-Rsp-Extension ::= SEQUENCE {
    velEstimate	 VelocityEstimate OPTIONAL,
    ganssLocationInfo	 GANSSLocationInfo OPTIONAL,
    ganssMeasureInfo	 GANSSMeasureInfo OPTIONAL,
    ...
}

GANSSLocationInfo ::= SEQUENCE {
    referenceFrame	 ReferenceFrame OPTIONAL,
    ganssTODm	 GANSSTODm OPTIONAL,
    ganssTODFrac	 INTEGER (0..16384) OPTIONAL,
    ganssTODUncertainty	 GANSSTODUncertainty OPTIONAL,
    ganssTimeID	 INTEGER (0..3) OPTIONAL,
    fixType	 FixType,
    posData	 PositionData,
    stationaryIndication	 INTEGER (0..1) OPTIONAL,
    posEstimate	 Ext-GeographicalInformation,
    ...
}

PositionData ::= BIT STRING {
    e-otd(0),
    gps(1),
    galileo(2)
} (SIZE(3..16))

GANSSTODm ::= INTEGER (0..3599999)

ReferenceFrame ::= SEQUENCE {
    referenceFN	 INTEGER (0..65535),
    referenceFNMSB	 INTEGER (0..63) OPTIONAL
}

GANSSMeasureInfo ::= SEQUENCE {
    ganssMsrSetList	 SeqOfGANSS-MsrSetElement
}

SeqOfGANSS-MsrSetElement ::= SEQUENCE (SIZE(1..3)) OF GANSS-MsrSetElement

GANSS-MsrSetElement ::= SEQUENCE {
    referenceFrame	 ReferenceFrame OPTIONAL,
    ganssTODm	 GANSSTODm OPTIONAL,
    deltaGNASSTOD	 INTEGER (0..127) OPTIONAL,
    ganssTODUncertainty	 GANSSTODUncertainty OPTIONAL,
    ganss-SgnTypeList	 SeqOfGANSS-SgnTypeElement
}

SeqOfGANSS-SgnTypeElement ::= SEQUENCE (SIZE(1..6)) OF GANSS-SgnTypeElement

GANSS-SgnTypeElement ::= SEQUENCE {
    ganssSignalID	 INTEGER (0..15),
    ganss-SgnList	 SeqOfGANSS-SgnElement
}

SeqOfGANSS-SgnElement ::= SEQUENCE (SIZE(1..16)) OF GANSS-SgnElement

GANSS-SgnElement ::= SEQUENCE {
    svID	 SVID,
    cNo	 INTEGER (0..63),
    mpathDet	 MpathIndic,
    carrierQualityInd	 INTEGER (0..3) OPTIONAL,
    codePhase	 INTEGER (0..2097151),
    integerCodePhase	 INTEGER (0..63) OPTIONAL,
    codePhaseRMSError	 INTEGER (0..63),
    doppler	 INTEGER (-32768..32767) OPTIONAL,
    adr	 INTEGER (0..33554431) OPTIONAL
}

Rel7-AssistanceData-Extension ::= SEQUENCE {
    ganss-AssistData	 GANSS-AssistData OPTIONAL,
    ganssCarrierPhaseMeasurementRequest	 NULL OPTIONAL,
    ganssTODGSMTimeAssociationMeasurementRequest	 NULL OPTIONAL,
    ...
}

Ext-GeographicalInformation ::= OCTET STRING (SIZE(1..maxExt-GeographicalInformation))

maxExt-GeographicalInformation INTEGER ::= 20

END

RRLP-Messages DEFINITIONS AUTOMATIC TAGS ::=
BEGIN

PDU ::= SEQUENCE {
    referenceNumber	 INTEGER (0..7),
    component	 RRLP-Component
}

RRLP-Component ::= CHOICE {
    msrPositionReq	 MsrPosition-Req,
    msrPositionRsp	 MsrPosition-Rsp,
    assistanceData	 AssistanceData,
    assistanceDataAck	 NULL,
    protocolError	 ProtocolError,
    ...
}

END

ULP-Components DEFINITIONS AUTOMATIC TAGS ::=
BEGIN

Version ::= SEQUENCE {
    maj	 INTEGER (0..255),
    min	 INTEGER (0..255),
    servind	 INTEGER (0..255)
}

SessionID ::= SEQUENCE {
    setSessionID	 SetSessionID OPTIONAL,
    slpSessionID	 SlpSessionID OPTIONAL
}

SetSessionID ::= SEQUENCE {
    sessionId	 INTEGER (0..65535),
    setId	 SETId
}

SETId ::= CHOICE {
    msisdn	 OCTET STRING (SIZE(8)),
    mdn	 OCTET STRING (SIZE(8)),
    min	 BIT STRING (SIZE(34)),
    imsi	 OCTET STRING (SIZE(8)),
    nai	 IA5String (SIZE(1..1000)),
    iPAddress	 IPAddress,
    ...
}

SlpSessionID ::= SEQUENCE {
    sessionID	 OCTET STRING (SIZE(4)),
    slpId	 SLPAddress
}

IPAddress ::= CHOICE {
    ipv4Address	 OCTET STRING (SIZE(4)),
    ipv6Address	 OCTET STRING (SIZE(16))
}

SLPAddress ::= CHOICE {
    iPAddress	 IPAddress,
    fQDN	 FQDN,
    ...
}

FQDN ::= VisibleString (FROM("a".."z" | "A".."Z" | "0".."9" | ".-"))(SIZE(1..255))

Ver ::= BIT STRING (SIZE(64))

LocationId ::= SEQUENCE {
    cellInfo	 CellInfo,
    status	 Status,
    ...
}

Status ::= ENUMERATED {
    stale(0),
    current(1),
    unknown(2),
    ...
}

CellInfo ::= CHOICE {
    gsmCell	 GsmCellInformation,
    wcdmaCell	 WcdmaCellInformation,
    cdmaCell	 CdmaCellInformation,
    ...
}

Position ::= SEQUENCE {
    timestamp	 UTCTime,
    positionEstimate	 PositionEstimate,
    velocity	 Velocity OPTIONAL,
    ...
}

PositionEstimate ::= SEQUENCE {
    latitudeSign	 ENUMERATED {
        north,    
        south
    },
    latitude	 INTEGER (0..8388607),
    longitude	 INTEGER (-8388608..8388607),
    uncertainty	 SEQUENCE {
        uncertaintySemiMajor	 INTEGER (0..127),    
        uncertaintySemiMinor	 INTEGER (0..127),    
        orientationMajorAxis	 INTEGER (0..180)
    } OPTIONAL,
    confidence	 INTEGER (0..100) OPTIONAL,
    altitudeInfo	 AltitudeInfo OPTIONAL,
    ...
}

AltitudeInfo ::= SEQUENCE {
    altitudeDirection	 ENUMERATED {
        height,    
        depth
    },
    altitude	 INTEGER (0..32767),
    altUncertainty	 INTEGER (0..127),
    ...
}

CdmaCellInformation ::= SEQUENCE {
    refNID	 INTEGER (0..65535),
    refSID	 INTEGER (0..32767),
    refBASEID	 INTEGER (0..65535),
    refBASELAT	 INTEGER (0..4194303),
    reBASELONG	 INTEGER (0..8388607),
    refREFPN	 INTEGER (0..511),
    refWeekNumber	 INTEGER (0..65535),
    refSeconds	 INTEGER (0..4194303),
    ...
}

GsmCellInformation ::= SEQUENCE {
    refMCC	 INTEGER (0..999),
    refMNC	 INTEGER (0..999),
    refLAC	 INTEGER (0..65535),
    refCI	 INTEGER (0..65535),
    nMR	 NMR OPTIONAL,
    tA	 INTEGER (0..255) OPTIONAL,
    ...
}

WcdmaCellInformation ::= SEQUENCE {
    refMCC	 INTEGER (0..999),
    refMNC	 INTEGER (0..999),
    refUC	 INTEGER (0..268435455),
    frequencyInfo	 FrequencyInfo OPTIONAL,
    primaryScramblingCode	 INTEGER (0..511) OPTIONAL,
    measuredResultsList	 MeasuredResultsList OPTIONAL,
    ...
}

FrequencyInfo ::= SEQUENCE {
    fmodeSpecificInfo	 CHOICE {
        fdd	 FrequencyInfoFDD,    
        tdd	 FrequencyInfoTDD,    
        ...
    },
    ...
}

FrequencyInfoFDD ::= SEQUENCE {
    uarfcn-UL	 UARFCN OPTIONAL,
    uarfcn-DL	 UARFCN,
    ...
}

FrequencyInfoTDD ::= SEQUENCE {
    uarfcn-Nt	 UARFCN,
    ...
}

UARFCN ::= INTEGER (0..16383)

NMR ::= SEQUENCE (SIZE(1..15)) OF NMRelement

NMRelement ::= SEQUENCE {
    aRFCN	 INTEGER (0..1023),
    bSIC	 INTEGER (0..63),
    rxLev	 INTEGER (0..63),
    ...
}

MeasuredResultsList ::= SEQUENCE (SIZE(1..maxFreq)) OF MeasuredResults

MeasuredResults ::= SEQUENCE {
    frequencyInfo	 FrequencyInfo OPTIONAL,
    utra-CarrierRSSI	 UTRA-CarrierRSSI OPTIONAL,
    cellMeasuredResultsList	 CellMeasuredResultsList OPTIONAL
}

CellMeasuredResultsList ::= SEQUENCE (SIZE(1..maxCellMeas)) OF CellMeasuredResults

UTRA-CarrierRSSI ::= INTEGER (0..127)

CellMeasuredResults ::= SEQUENCE {
    cellIdentity	 INTEGER (0..268435455) OPTIONAL,
    modeSpecificInfo	 CHOICE {
        fdd	 SEQUENCE {
            primaryCPICH-Info	 PrimaryCPICH-Info,        
            cpich-Ec-N0	 CPICH-Ec-N0 OPTIONAL,        
            cpich-RSCP	 CPICH-RSCP OPTIONAL,        
            pathloss	 Pathloss OPTIONAL
        },    
        tdd	 SEQUENCE {
            cellParametersID	 CellParametersID,        
            proposedTGSN	 TGSN OPTIONAL,        
            primaryCCPCH-RSCP	 PrimaryCCPCH-RSCP OPTIONAL,        
            pathloss	 Pathloss OPTIONAL,        
            timeslotISCP-List	 TimeslotISCP-List OPTIONAL
        }
    }
}

CellParametersID ::= INTEGER (0..127)

TGSN ::= INTEGER (0..14)

PrimaryCCPCH-RSCP ::= INTEGER (0..127)

TimeslotISCP ::= INTEGER (0..127)

TimeslotISCP-List ::= SEQUENCE (SIZE(1..maxTS)) OF TimeslotISCP

PrimaryCPICH-Info ::= SEQUENCE {
    primaryScramblingCode	 INTEGER (0..511)
}

CPICH-Ec-N0 ::= INTEGER (0..63)

CPICH-RSCP ::= INTEGER (0..127)

Pathloss ::= INTEGER (46..173)

maxCellMeas INTEGER ::= 32

maxFreq INTEGER ::= 8

maxTS INTEGER ::= 14

QoP ::= SEQUENCE {
    horacc	 INTEGER (0..127),
    veracc	 INTEGER (0..127) OPTIONAL,
    maxLocAge	 INTEGER (0..65535) OPTIONAL,
    delay	 INTEGER (0..7) OPTIONAL,
    ...
}

Velocity ::= CHOICE {
    horvel	 Horvel,
    horandvervel	 Horandvervel,
    horveluncert	 Horveluncert,
    horandveruncert	 Horandveruncert,
    ...
}

Horvel ::= SEQUENCE {
    bearing	 BIT STRING (SIZE(9)),
    horspeed	 BIT STRING (SIZE(16)),
    ...
}

Horandvervel ::= SEQUENCE {
    verdirect	 BIT STRING (SIZE(1)),
    bearing	 BIT STRING (SIZE(9)),
    horspeed	 BIT STRING (SIZE(16)),
    verspeed	 BIT STRING (SIZE(8)),
    ...
}

Horveluncert ::= SEQUENCE {
    bearing	 BIT STRING (SIZE(9)),
    horspeed	 BIT STRING (SIZE(16)),
    uncertspeed	 BIT STRING (SIZE(8)),
    ...
}

Horandveruncert ::= SEQUENCE {
    verdirect	 BIT STRING (SIZE(1)),
    bearing	 BIT STRING (SIZE(9)),
    horspeed	 BIT STRING (SIZE(16)),
    verspeed	 BIT STRING (SIZE(8)),
    horuncertspeed	 BIT STRING (SIZE(8)),
    veruncertspeed	 BIT STRING (SIZE(8)),
    ...
}

StatusCode ::= ENUMERATED {
    unspecified(0),
    systemFailure(1),
    unexpectedMessage(2),
    protocolError(3),
    dataMissing(4),
    unexpectedDataValue(5),
    posMethodFailure(6),
    posMethodMismatch(7),
    posProtocolMismatch(8),
    targetSETnotReachable(9),
    versionNotSupported(10),
    resourceShortage(11),
    invalidSessionId(12),
    nonProxyModeNotSupported(13),
    proxyModeNotSupported(14),
    positioningNotPermitted(15),
    authNetFailure(16),
    authSuplinitFailure(17),
    consentDeniedByUser(100),
    consentGrantedByUser(101),
    ...
}

PosMethod ::= ENUMERATED {
    agpsSETassisted(0),
    agpsSETbased(1),
    agpsSETassistedpref(2),
    agpsSETbasedpref(3),
    autonomousGPS(4),
    aFLT(5),
    eCID(6),
    eOTD(7),
    oTDOA(8),
    noPosition(9),
    ...
}

END

SUPL-END DEFINITIONS AUTOMATIC TAGS ::=
BEGIN

SUPLEND ::= SEQUENCE {
    position	 Position OPTIONAL,
    statusCode	 StatusCode OPTIONAL,
    ver	 Ver OPTIONAL,
    ...
}

END

SUPL-INIT DEFINITIONS AUTOMATIC TAGS ::=
BEGIN

SUPLINIT ::= SEQUENCE {
    posMethod	 PosMethod,
    notification	 Notification OPTIONAL,
    sLPAddress	 SLPAddress OPTIONAL,
    qoP	 QoP OPTIONAL,
    sLPMode	 SLPMode,
    mAC	 MAC OPTIONAL,
    keyIdentity	 KeyIdentity OPTIONAL,
    ...
}

Notification ::= SEQUENCE {
    notificationType	 NotificationType,
    encodingType	 EncodingType OPTIONAL,
    requestorId	 OCTET STRING (SIZE(1..maxReqLength)) OPTIONAL,
    requestorIdType	 FormatIndicator OPTIONAL,
    clientName	 OCTET STRING (SIZE(1..maxClientLength)) OPTIONAL,
    clientNameType	 FormatIndicator OPTIONAL,
    ...
}

NotificationType ::= ENUMERATED {
    noNotificationNoVerification(0),
    notificationOnly(1),
    notificationAndVerficationAllowedNA(2),
    notificationAndVerficationDeniedNA(3),
    privacyOverride(4),
    ...
}

EncodingType ::= ENUMERATED {
    ucs2(0),
    gsmDefault(1),
    utf8(2),
    ...
}

maxReqLength INTEGER ::= 50

maxClientLength INTEGER ::= 50

FormatIndicator ::= ENUMERATED {
    logicalName(0),
    e-mailAddress(1),
    msisdn(2),
    url(3),
    sipUrl(4),
    min(5),
    mdn(6),
    imsPublicIdentity(7),
    ...
}

SLPMode ::= ENUMERATED {
    proxy(0),
    nonProxy(1)
}

MAC ::= BIT STRING (SIZE(64))

KeyIdentity ::= BIT STRING (SIZE(128))

END

SUPL-POS DEFINITIONS AUTOMATIC TAGS ::=
BEGIN

SUPLPOS ::= SEQUENCE {
    posPayLoad	 PosPayLoad,
    velocity	 Velocity OPTIONAL,
    ...
}

PosPayLoad ::= CHOICE {
    tia801payload	 OCTET STRING (SIZE(1..8192)),
    rrcPayload	 OCTET STRING (SIZE(1..8192)),
    rrlpPayload	 OCTET STRING (SIZE(1..8192)),
    ...
}

END

SUPL-POS-INIT DEFINITIONS AUTOMATIC TAGS ::=
BEGIN

SUPLPOSINIT ::= SEQUENCE {
    sETCapabilities	 SETCapabilities,
    requestedAssistData	 RequestedAssistData OPTIONAL,
    locationId	 LocationId,
    position	 Position OPTIONAL,
    sUPLPOS	 SUPLPOS OPTIONAL,
    ver	 Ver OPTIONAL,
    ...
}

RequestedAssistData ::= SEQUENCE {
    almanacRequested	 BOOLEAN,
    utcModelRequested	 BOOLEAN,
    ionosphericModelRequested	 BOOLEAN,
    dgpsCorrectionsRequested	 BOOLEAN,
    referenceLocationRequested	 BOOLEAN,
    referenceTimeRequested	 BOOLEAN,
    acquisitionAssistanceRequested	 BOOLEAN,
    realTimeIntegrityRequested	 BOOLEAN,
    navigationModelRequested	 BOOLEAN,
    navigationModelData	 XNavigationModel OPTIONAL,
    ...
}

XNavigationModel ::= SEQUENCE {
    gpsWeek	 INTEGER (0..1023),
    gpsToe	 INTEGER (0..167),
    nSAT	 INTEGER (0..31),
    toeLimit	 INTEGER (0..10),
    satInfo	 SatelliteInfo OPTIONAL,
    ...
}

SatelliteInfo ::= SEQUENCE (SIZE(1..31)) OF SatelliteInfoElement

SatelliteInfoElement ::= SEQUENCE {
    satId	 INTEGER (0..63),
    iODE	 INTEGER (0..255),
    ...
}

END

SUPL-RESPONSE DEFINITIONS AUTOMATIC TAGS ::=
BEGIN

SUPLRESPONSE ::= SEQUENCE {
    posMethod	 PosMethod,
    sLPAddress	 SLPAddress OPTIONAL,
    sETAuthKey	 SETAuthKey OPTIONAL,
    keyIdentity4	 KeyIdentity4 OPTIONAL,
    ...
}

SETAuthKey ::= CHOICE {
    shortKey	 BIT STRING (SIZE(128)),
    longKey	 BIT STRING (SIZE(256)),
    ...
}

KeyIdentity4 ::= BIT STRING (SIZE(128))

END

SUPL-START DEFINITIONS AUTOMATIC TAGS ::=
BEGIN

SUPLSTART ::= SEQUENCE {
    sETCapabilities	 SETCapabilities,
    locationId	 LocationId,
    qoP	 QoP OPTIONAL,
    ...
}

SETCapabilities ::= SEQUENCE {
    posTechnology	 PosTechnology,
    prefMethod	 PrefMethod,
    posProtocol	 PosProtocol,
    ...
}

PosTechnology ::= SEQUENCE {
    agpsSETassisted	 BOOLEAN,
    agpsSETBased	 BOOLEAN,
    autonomousGPS	 BOOLEAN,
    aFLT	 BOOLEAN,
    eCID	 BOOLEAN,
    eOTD	 BOOLEAN,
    oTDOA	 BOOLEAN,
    ...
}

PrefMethod ::= ENUMERATED {
    agpsSETassistedPreferred,
    agpsSETBasedPreferred,
    noPreference
}

PosProtocol ::= SEQUENCE {
    tia801	 BOOLEAN,
    rrlp	 BOOLEAN,
    rrc	 BOOLEAN,
    ...
}

END

ULP DEFINITIONS AUTOMATIC TAGS ::=
BEGIN

ULP-PDU ::= SEQUENCE {
    length	 INTEGER (0..65535),
    version	 Version,
    sessionID	 SessionID,
    message	 UlpMessage
}

UlpMessage ::= CHOICE {
    msSUPLINIT	 SUPLINIT,
    msSUPLSTART	 SUPLSTART,
    msSUPLRESPONSE	 SUPLRESPONSE,
    msSUPLPOSINIT	 SUPLPOSINIT,
    msSUPLPOS	 SUPLPOS,
    msSUPLEND	 SUPLEND,
    msDUMMY2	 DUMMY,
    msDUMMY3	 DUMMY,
    ...
}

DUMMY ::= INTEGER

END
